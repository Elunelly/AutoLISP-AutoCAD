(defun c:DIG_BURST (/ *error* n layers $ CTAB CLAYER jsel lst)
  (defun *error* (msg)
    (if lst (mapcar '(lambda (l) (vlax-put l 'Lock -1)) lst))
    (mapcar 'setvar '("CTAB" "CLAYER") (list CTAB CLAYER))
    (if $ (vla-delete $))
    (princ msg)
  )
  (initget 4)
  (setq
    n (getint "\nNombre d'imbrication maximale <Tout> : ")
    layers (vla-get-layers (vla-get-ActiveDocument (vlax-get-acad-object)))
    $ (vla-add layers "$tmp$")
    CTAB (getvar "CTAB")
    CLAYER (getvar "CLAYER")
  )
  (mapcar 'setvar '("CTAB" "CLAYER") '("Model" "$tmp$"))
  (vlax-for layer layers
    (if (and (not (wcmatch (vla-get-Name layer) "*|*,$tmp$")) (/= 0 (vlax-get layer 'Lock)))
      (progn
        (vlax-put layer 'Lock 0)
        (setq lst (cons layer lst))
      )
    )
  )
  (while
    (and
      (or (null n) (not (zerop (1+ n))))
      (setq jsel (ssget "_X" '((0 . "INSERT") (410 . "Model"))))
    )
    (sssetfirst nil jsel)
    (c:BURST)
    (setq n (1- n))
  )
  (mapcar '(lambda (l) (vlax-put l 'Lock -1)) lst)
  (mapcar 'setvar '("CTAB" "CLAYER") (list CTAB CLAYER))
  (setq $ (vla-delete $))
  (princ)
)

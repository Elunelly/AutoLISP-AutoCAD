(defun c:COPYCOT (/ jsel name fuzz entlist rep dim xdt pos pre suf txt)
  (and
    (setq jsel (ssget "_+.:E:S" '((0 . "DIMENSION"))))
    (setq name (ssname jsel 0))
    (setq fuzz (vla-get-PrimaryUnitsPrecision (vlax-ename->vla-object name)))
    (setq entlist (entget name '("ACAD")))
    (setq rep (cdr (assoc 1 entlist)))
    (setq dim (cdr (assoc 42 entlist)))
    (setq xdt (cdadr (assoc -3 entlist)))
    (setq xdt (cdr (assoc 1000 (cdr xdt))))
    (setq pos (vl-string-search "<>" xdt))
    (setq pre (cond ((= pos 0) "") ((substr xdt 1 pos))))
    (setq suf (cond ((= (setq pos (+ pos 2)) (strlen xdt)) "") ((substr xdt (1+ pos)))))
    (setq txt (strcat pre (rtos dim 2 fuzz) suf))
    (setq pos (vl-string-search "<>" rep))
    (setq txt
      (cond
        ( (= 2 (strlen rep)) txt)
        ( (= pos 0)
          (strcat txt (substr rep 2))
        )
        ( (= (+ pos 2) (strlen rep))
          (strcat (substr rep 1 pos) txt)
        )
        ( (strcat (substr rep 1 pos) txt (substr rep (+ pos 3))))
      )
    )
    (setq jsel (ssget "_+.:E:S" '((0 . "MTEXT,TEXT"))))
    (setq name (ssname jsel 0))
    (entmod (subst (cons 1 txt) (assoc 1 (entget name)) (entget name)))
    (princ "\nLe texte de cotation a été copié avec succès")
  )
  (princ)
)

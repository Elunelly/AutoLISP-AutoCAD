(defun copy-Att (blk-src tag-src blk-tgt tag-tgt / ConvEnt get-att-list check LM:vl-SetAttributeValue value)
  (defun ConvEnt (name flag / tp)
    (if (= (setq tp (type name)) flag)
      name
      (apply (read (strcat "vlax-" (vl-symbol-name tp) "->" (vl-symbol-name flag))) (list name))
    )
  )
  (defun get-att-list (name)
    (mapcar '(lambda (a) (cons (vla-get-tagstring a) (vla-get-textstring a))) (vlax-invoke (ConvEnt name 'VLA-OBJECT) 'getAttributes))
  )
  (defun check (blk tag / att value)
    (and
      (= "AcDbBlockReference" (vla-get-ObjectName (ConvEnt blk 'VLA-OBJECT)))
      (setq att (get-att-list blk))
      (assoc tag att)
      (setq value (cdr (assoc tag att)))
    )
    value
  )
  (defun LM:vl-SetAttributeValue (blk tag val)
    (setq tag (strcase tag))
    (vl-some
      '(lambda (att)
        (if (= tag (strcase (vla-get-tagstring att)))
          (progn (vla-put-textstring att val) val)
        )
       )
      (vlax-invoke blk 'getAttributes)
    )
  )
  (and
    (setq value (check blk-src tag-src))
    (check blk-tgt tag-tgt)
    (LM:vl-SetAttributeValue (ConvEnt blk-tgt 'VLA-OBJECT) tag-tgt value)
  )
)

(defun c:AH (/ acc mode pt obj txt)
  (setq acc (getvar "OSMODE"))
  (setvar "OSMODE" 0)
  (initget "Supprimer Conserver")
  (setq mode (cond ((getkword "\nSupprimer ou conserver le contour ? [Supprimer/Conserver] <Conserver> : ")) ("Conserver")))
  (command "_-BOUNDARY" (setq pt (getpoint "\nSpécifiez un point interne : ")) "")
  (setq obj (vlax-ename->vla-object (entlast)))
  (cond
    ( (= "Supprimer" mode)
      (setq txt (rtos (vla-get-area obj)))
      (entdel (entlast))
    )
    ( (= "Conserver" mode)
      (setq txt (strcat "%<\\AcObjProp Object(%<\\_ObjId " (itoa (vla-get-ObjectID obj)) ">%).Area \\f \"%lu2\">%"))
    )
  )
  (command "_-HATCH" "_Properties" "ANSI31" "" "" pt "")
  (command "_-TEXT" "_Justify" "_MC" pt "" "" txt)
  (setvar "OSMODE" acc)
  (princ)
)

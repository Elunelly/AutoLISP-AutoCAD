(defun c:GREYLAY (/ *error* RGB->GREY cmdecho layers name layer color rgb grey)
  (defun *error* (msg)
    (setvar "CMDECHO" cmdecho)
    (princ msg)
  )
  (defun RGB->GREY (RGB / c)
    (if
      (and
        (listp RGB)
        (= 3 (length RGB))
        (not (member nil (mapcar '(lambda (x) (<= 0 x 255)) RGB)))
        (setq c (LM:round (/ (apply '+ RGB) 3.)))
      )
      (list c c c)
    )
  )
  (setq doc (vla-get-ActiveDocument (vlax-get-acad-object)))
  (vla-StartUndoMark doc)
  (setvar "TILEMODE" 0)
  (setq cmdecho (getvar "CMDECHO"))
  (setq layers (vla-get-Layers (vla-get-ActiveDocument (vlax-get-acad-object))))
  (if (/= 1 (getvar "CVPORT"))
    (progn
      (while (setq name (car (nentsel)))
        (setq
          layer (cdr (assoc 8 (entget name)))
          color (vla-get-TrueColor (vla-item layers layer))
          rgb (list (vla-get-Red color) (vla-get-Green color) (vla-get-Blue color))
          grey (lst2str (RGB->GREY rgb) ",")
        )
        (setvar "CMDECHO" 0)
        (command "_VPLAYER" "_Color" "_TrueColor" grey layer "_Current" "")
        (setvar "CMDECHO" cmdecho)
        (princ
          (strcat
            (LgT "\nLayer's color modification of \"" "\nModification de la couleur du calque \"" nil)
            layer
            (LgT "\" from " "\" de " nil)
            (lst2str rgb ",")
            (LgT " to " " en " nil)
            grey
          )
        )
      )
    )
  )
  (vla-EndUndoMark doc)
  (princ)
)

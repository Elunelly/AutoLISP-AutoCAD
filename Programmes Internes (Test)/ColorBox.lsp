(defun c:CAMvision (CAM HTc PRc / getCAMvision PTc CN1 CN2 PT1 PT2 EL1 EL2 DS1 DS2 ALT break lay lst jsel i name)
  (defun getCAMvision (name)
  )
  (setq
    PTc (cdr (assoc 10 (entget CAM)))
    CN1 (car (entsel "\nSelect the first CN : "))
    CN2 (car (entsel "\nSelect the second CN : "))
    PT1 (vlax-curve-getClosestPointTo CN1 PtC)
    PT2 (vlax-curve-getClosestPointTo CN2 PtC)
    EL1 (cdr (assoc 38 (entget CN1)))
    EL2 (cdr (assoc 38 (entget CN2)))
    DS1 (distance (reverse (cdr (reverse PTc))) (reverse (cdr (reverse PT1))))
    DS2 (distance (reverse (cdr (reverse PTc))) (reverse (cdr (reverse PT2))))
    ALT (+ EL1 (* (- EL2 EL1) (/ DS1 (+ DS1 DS2))))
  )
  (while (not break)
    (setq name (getkdh (quote (entsel msg)) "\nSelect a CN polyline or an obstacle" '("eXit") " : " "eXit" nil))
    (cond
      ( (= "eXit" name) (setq break T))
      ( (and
          name
          (member (cdr (assoc 0 (entget name))) '("LWPOLYLINE" "POLYLINE"))
        )
        (if (member (setq lay (cdr (assoc 8 (entget name)))) lst)
          (princ (strcat "\nThe layer \"" lay "\" is already selected..."))
          (setq lst (cons lay lst))
        )
      )
    )
  )
  (if (setq jsel (ssget "_X" (list '(0 . "LWPOLYLINE, POLYLINE") (cons 8 (lst2str lst ",")) '(410 . "Model"))))
    (progn
      (repeat (setq i (sslength jsel))
        (setq name (ssname jsel (setq i (1- i))))
        (getCAMvision name)
      )
    )
  )
)

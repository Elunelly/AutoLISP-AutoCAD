; +-----------------------------------------------------------------------------------------------------------------------------------------------+ ;
; |                                                                                                                                               | ;
; |                                                HELP FILE FOR DEVELOPPERS FOR COMMAND'S CREATION                                               | ;
; |                                                                                                                                               | ;
; +-----------------------------------------------------------------------------------------------------------------------------------------------+ ;



;                                                   []-----------------------------------------[]                                                   ;

; Command's classification based on their functionnality and utility (from "Reference Guide for Developpers", Help center) :                        ;
;                                                                                                                                                   ;
;                                                                 --- Paperspace ---                                                                ;
;--- Commands based on the manipulation of objects localized in layouts (viewports, title-blocks, layouts, ...)                                     ;
;   --•  Title Block-Handling                   >  "PsUcart"                                                                                        ;
;   --•  Viewport-Handling                      >  "PsViewp"                                                                                        ;
;   --•  Layout-Handling                        >  "PsLaytb"                                                                                        ;
;                                                                                                                                                   ;
;                                                        --- Symbol table and Dictionary ---                                                        ;
;--- Commands based on the manipulation of Symbol Table ("LAYER", "BLOCK", ...), XDatas and dictionaries-handling, ...                              ;
;   --•  Block List-Handling                    >  "SdBlock"                                                                                        ;
;   --•  Layer List-Handling                    >  "SdLayer"                                                                                        ;
;   --•  Extended Data-Handling                 >  "SdXdata"                                                                                        ;
;                                                                                                                                                   ;
;                                                                  --- Utility ---                                                                  ;
;--- Commands based on the modification of object's properties, geometric's datas, system's variables, ...                                          ;
;   --•  File-Handling                          >  "UtFiles"                                                                                        ;
;   --•  Geometric Data                         >  "UtGeodt"                                                                                        ;
;   --•  Object-Handling                        >  "UtObjet"                                                                                        ;
;   --•  System Variable-Handling               >  "UtVarsy"                                                                                        ;
;                                                                                                                                                   ;
;                                                       --- Selection Set and Bounding box ---                                                      ;
;--- Commands based on the manipulation of selection set and bounding box                                                                           ;
;   --•  Bounding Box                           >  "BbBound"                                                                                        ;
;   --•  Selection Set Manipulation             >  "BbSelct"                                                                                        ;
;                                                                                                                                                   ;

;                                                   []-----------------------------------------[]                                                   ;

;--- Common local variable's name for the programs (Declare all the local variable of programs is not an option !)                                  ;
;                                                                                                                                                   ;
;                                                                   --- Entity ---                                                                  ;
;   --•  name         > Entity name as <Nom d'entité: ab2e580> (= primary ename)                                                                    ;
;   --•  vl-name      > Entity name as #<VLA-OBJECT IAcadBlockReference 0000000038584688> (= primary VLA-Object)                                    ;
;   --•  ent          > Entity name as <Nom d'entité: ab2e580> (= secondary ename)                                                                  ;
;   --•  vl-ent       > Entity name as #<VLA-OBJECT IAcadBlockReference 0000000038584688> (= secondary VLA-Object)                                  ;
;   --•  entlist      > DXF list obtained with (entget)                                                                                             ;
;   --•  newlist      > DXF list modified or obtained with (entmod) when you want to keep the 'entlist' value                                       ;
;                                                                                                                                                   ;
;                                                               --- Selection Set ---                                                               ;
;   --•  jsel         > Selection set name as <Selection set: 7a> (= primary name)                                                                  ;
;   --•  ssel         > Selection set name as <Selection set: 7a> (= secondary name)                                                                ;
;                                                                                                                                                   ;
;                                                                  --- Counter ---                                                                  ;
;   --•  i            > Counting variable for loop (while), (repeat), (foreach), ... or the number of objects                                       ;
;   --•  n            > Counting variable for the numbering of objects or their position in a list                                                  ;
;                                                                                                                                                   ;
;                                                                    --- List ---                                                                   ;
;   --•  lst          > List for global use, generally obtained by using (cons) in a loop (= primary name)                                          ;
;   --•  pt-list      > List of points coordinates, generally obtained by using (get-pt-list)                                                       ;
;   --•  att-list     > List of block's attributes, generally obtained by using (get-att-list)                                                      ;
;   --•  dyn-list     > List of block's dynamic properties, generally obtained by using (get-DynProp-list)                                          ;
;   --•  layout-list  > List of layouts, generally obtained by using (layoutlist)                                                                   ;
;   --•  layer-list   > List of layers, generally obtained by using (flt_tbl "LAYER")                                                               ;
;   --•  bloc-list    > List of block's definitions, generally obtained by using (flt_tbl "BLOCK")                                                  ;
;                                                                                                                                                   ;
;                                                                   --- String ---                                                                  ;
;   --•  str          > String for global use, generally used for (substr)                                                                          ;
;   --•  msg          > String used for prompting a message in command line's historic, alert message, error's message or dialog_box                ;
;   --•  search       > String used for relative search, generally used for (wcmatch)                                                               ;
;   --•  tag          > Key of pair list, generally used as search key for (assoc)                                                                  ;
;   --•  value        > Value of pair list, generally associated with a search key for (assoc)                                                      ;
;   --•  *-old        > String representing an old value                                                                                            ;
;   --•  *-new        > String representing a new value                                                                                             ;
;                                                                                                                                                   ;
;                                                                 --- Geometric ---                                                                 ;
;   --•  pt           > Coordinates (x y) or (x y z) of a point, generally obtained by using (getpoint)                                             ;
;   --•  ang          > Angle expressed in radian, generally used for (polar)                                                                       ;
;   --•  dist         > Algebric distance, generally used for (vlax-curve-) or (polar)                                                              ;
;                                                                                                                                                   ;
;                                                               --- Loop Variable ---                                                               ;
;   --•  x            > Variable associated for common use of (mapcar '(lambda)) for single argument                                                ;
;   --•  layout       > Name of a specific layout, generally used for (foreach)                                                                     ;
;   --•  layer        > Name of a specific layer, generally used for (foreach)                                                                      ;
;   --•  blc          > Name of a specific block, generally used for (foreach)                                                                      ;
;                                                                                                                                                   ;
;                                                                   --- Method ---                                                                  ;
;   --•  mode         > Value specified by user with (getkword) to determine how the program will work with (cond)                                  ;
;   --•  chx          > Answer specified by user with (getkword) to a "Yes/No" question, could be use with (while)                                  ;
;   --•  flag         > Numeric value (integer) to determine the global functionnality of a function                                                ;
;                                                                                                                                                   ;

;                                                   []-----------------------------------------[]                                                   ;

;--- Some tips for good using the command's file definition :                                                                                       ;
;                                                                                                                                                   ;
;                                                            --- Version of commands ---                                                            ;
; Each command possess a specific string representing the version number. After any modification, this version number have to be updated properly.  ;
; At the creation of a named command (for common use), a new file will be created based on the model file "_XxXxxxx . CommandName.lsp" with all the ;
; informations needed in commentaries.                                                                                                              ;
;   --•  _XxXxxxx     > represents the classification's code, like "PsUcart", "UtVarsy", ... for example                                            ;
;   --•  CommandName  > represents the name of the command defined in the file                                                                      ;
; For each modification, an explanation of what was modified since the last modification is needed. For that, you will need to write the version    ;
; number with the explanation next to the last line.                                                                                                ;
; An update of the file "Developpement LISP - Fichier de suivi" will be needed as soon as possible !                                                ;
;                                                                                                                                                   ;
; Each version number are based on 3 digit, spaced by a ".", representing each modification level -> #.#.#                                          ;
; See the following explanation for each modification level and how version number works :                                                          ;
;   --•  Level n°1 - Major modification                                                                                                             ;
;     It's corresponding to the first digit of the version number. It's concerning any addition or suppression of one or several functionnalities   ;
;     that have a influence on the global use of the command. For a major modification, level 2 and 3 are reset to 0.                               ;
;                                                                                                                                                   ;
;   --•  Level n°2 - Intermediate modification                                                                                                      ;
;     It's corresponding to the second digit of the version number. It's concerning any modifications on existing functionnalities but if the use   ;
;     the command is changed from the point of view of the user, it's considered as a major modification (like addition or suppression of user's    ;
;     input). For a intermediate modification, level 3 is reset to 0.                                                                               ;
;                                                                                                                                                   ;
;   --•  Level n°3 - Minor modification                                                                                                             ;
;     It's corresponding to the third digit of the version number. It's concerning any bug's correction, writing simplification, addition or        ;
;     suppression of variable type check, ... Any modification of use will be considered as intermediate modification (level 2).                    ;
;                                                                                                                                                   ;
;                                                          --- Existing command's list ---                                                          ;
;   --•  "PsUcart" --> NAMECART                                     | v#.#.# - ##/##/#### (Luna)                                                    ;
;   --•  "PsUcart" --> MODCART                                      | v#.#.# - ##/##/#### (Luna)                                                    ;
;   --•  "PsUcart" --> DATECART                                     | v#.#.# - ##/##/#### (Luna)                                                    ;
;   --•  "PsUcart" --> FLTCART                                      | v#.#.# - ##/##/#### (Luna)                                                    ;
;   --•  "PsViewp" --> RADPURGE                                     | v#.#.# - ##/##/#### (Luna)                                                    ;
;   --•  "PsViewp" --> VP-RADPURGE                                  | v#.#.# - ##/##/#### (Luna)                                                    ;
;   --•  "PsViewp" --> FNTAERIENNE                                  | v#.#.# - ##/##/#### (Luna)                                                    ;
;   --•  "PsViewp" --> VP-COPYLAYERLIST                             | v#.#.# - ##/##/#### (Luna)                                                    ;
;                                                                                                                                                   ;
;   --•  "SdLayer" --> MAJCALQUE                                    | v#.#.# - ##/##/#### (Luna)                                                    ;
;                                                                                                                                                   ;
;   --•  "UtGeodt" --> LONGCUMUL                                    | v#.#.# - ##/##/#### (Luna)                                                    ;
;   --•  "UtGeodt" --> SIMPLAREA                                    | v#.#.# - ##/##/#### (Luna)                                                    ;
;   --•  "UtGeodt" --> PV-ENTRAXE                                   | v1.1.1 - 22/06/2020 (Luna)                                                    ;
;   --•  "UtGeodt" --> ARRAYCOUNT                                   | v#.#.# - ##/##/#### (Luna)                                                    ;
;   --•  "UtObjet" --> POLYDELPOINT                                 | v#.#.# - ##/##/#### (Luna)                                                    ;
;   --•  "UtObjet" --> POLYADDPOINT                                 | v#.#.# - ##/##/#### (Luna)                                                    ;
;   --•  "UtObjet" --> PLINE3DTO2D                                  | v#.#.# - ##/##/#### (Luna)                                                    ;
;   --•  "UtObjet" --> ALTPOINT                                     | v#.#.# - ##/##/#### (Luna)                                                    ;
;   --•  "UtObjet" --> ATT-INCR                                     | v#.#.# - ##/##/#### (Luna)                                                    ;
;   --•  "UtObjet" --> SETCOLOR                                     | v#.#.# - ##/##/#### (Luna)                                                    ;
;   --•  "UtVarsy" --> RPCUSTOM                                     | v#.#.# - ##/##/#### (Didier)                                                  ;
;   --•  "UtVarsy" --> PSLTSCALECUSTOM                              | v#.#.# - ##/##/#### (Luna)                                                    ;
;                                                                                                                                                   ;
;   --•  "BbBound" --> BUBBLE                                       | v#.#.# - ##/##/#### (Luna)                                                    ;
;   --•  "BbSelct" --> NEWSELECT                                    | v#.#.# - ##/##/#### (Luna)                                                    ;
;                                                                                                                                                   ;

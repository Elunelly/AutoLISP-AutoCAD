; +-----------------------------------------------------------------------------------------------------------------------------------------------+ ;
; |                                                                                                                                               | ;
; |                                               HELP FILE FOR DEVELOPPERS FOR FUNCTION'S CREATION                                               | ;
; |                                                                                                                                               | ;
; +-----------------------------------------------------------------------------------------------------------------------------------------------+ ;



;                                                   []-----------------------------------------[]                                                   ;

; Function's classification based on their functionnality and utility (from "Reference Guide for Developpers", Help center) :                       ;
;                                                                                                                                                   ;
;                                                                   --- Basic ---                                                                   ;
; Functions based on mathematical calculation, manipulation of lists and strings, conditions, error-handling, ...                                   ;
;   --•  Application-Handling                   > "BaApp"           (4x0,40+0x0,00)/13   = 0,1231                                                   ;
;   --•  Arithmetic                             > "BaAri"           (24x0,80+7x0,45)/26  = 0,8596                                                   ;
;   --•  Equality and Conditionnals             > "BaEqc"           (14x0,85+2x0,60)/15  = 0,8733                                                   ;
;   --•  Error-Handling                         > "BaErr"           (6x0,80+0x0,00)/10   = 0,4800                                                   ;
;   --•  Function-Handling                      > "BaFun"           (5x0,95+1x0,75)/10   = 0,5500                                                   ;
;   --•  List Manipulation                      > "BaLst"           (28x0,90+13x0,85)/33 = 1,0985                                                   ;
;   --•  String Manipulation                    > "BaStr"           (15x0,80+6x0,60)/18  = 0,8667                                                   ;
;   --•  Symbol-Handling                        > "BaSym"           (12x0,85+0x0,00)/13  = 0,7846                                                   ;
;                                                                                                                                                   ;
;                                                                  --- Utility ---                                                                  ;
; Functions based on data conversion, user input, information display, ...                                                                          ;
;   --•  Data Conversion                        > "UtDac"           (11x0,85+4x0,90)/11  = 1,1773                                                   ;
;   --•  Device Access                          > "UtDev"           (1x0,25+0x0,00)/2    = 0,1250                                                   ;
;   --•  Display Control                        > "UtDis"           (7x0,40+1x0,60)/15   = 0,2267                                                   ;
;   --•  File-Handling                          > "UtFil"           (7x0,50+1x0,45)/19   = 0,2079                                                   ;
;   --•  Geometric                              > "UtGeo"           (5x0,95+2x0,50)/6    = 0,9583                                                   ;
;   --•  Query and Command                      > "UtCom"           (7x0,40+0x0,00)/17   = 0,1647                                                   ;
;   --•  Memory Management                      > "UtMem"           (0x0,00+0x0,00)/4    = 0,0000                                                   ;
;   --•  User Input                             > "UtUse"           (14x1,00+2x0,90)/14  = 1,1286                                                   ;
;   --•  Windows Registry                       > "UtWin"           (0x0,00+2x0,20)/7    = 0,0571                                                   ;
;                                                                                                                                                   ;
;                                                   --- Selection Set, Object and Symbol Table ---                                                  ;
; Functions based on extended data, selection set and object manipulation, Symbol Table manipulation, dictionary-handling, ...                      ;
;   --•  Extended Data-Handling                 > "DtXdt"           (1x0,75+0x0,00)/3    = 0,2500                                                   ;
;   --•  Object-Handling                        > "DtObj"           (17x0,90+7x0,95)/22  = 0,9977                                                   ;
;   --•  Selection Set Manipulation             > "DtSel"           (9x0,90+2x0,85)/9    = 1,0889                                                   ;
;   --•  Symbol Table and Dictionary-Handling   > "DtSyt"           (13x0,70+1x0,60)/17  = 0,5706                                                   ;
;                                                                                                                                                   ;
;                                                      --- Programmable Dialog Boxes - DCL ---                                                      ;
; Functions based on dialog box-handling (DCL and LSP files)                                                                                        ;
;   --•  Dialog Box Opening and Closing         > "DbOpc"           (5x0,90+0x0,00)/6    = 0,7500                                                   ;
;   --•  Tile and Attribute-Handling            > "DbTil"           (4x0,95+0x0,00)/5    = 0,7600                                                   ;
;   --•  List Box and Pop-up List-Handling      > "DbLst"           (3x1,00+1x0,80)/3    = 1,2667                                                   ;
;   --•  Image Tile-Handling                    > "DbImg"           (5x0,20+0x0,00)/7    = 0,1429                                                   ;
;   --•  Application-Specific Data-Handling     > "DbApp"           (0x0,00+0x0,00)/1    = 0,0000                                                   ;
;                                                                                                                                                   ;
;                                                    --- Visual LISP Extensions for AutoLISP ---                                                    ;
; Functions based on ActiveX/COM APIs for AutoCAD                                                                                                   ;
;   --•  ActiveX Collection Manipulation        > "VlCol"           (1x0,30+1x0,60)/2    = 0,4500                                                   ;
;   --•  ActiveX Data Conversion                > "VlDtc"           (11x0,25+1x0,75)/17  = 0,2059                                                   ;
;   --•  ActiveX Method Invocation              > "VlMet"           (2x0,50+0x0,00)/2    = 0,5000                                                   ;
;   --•  ActiveX Object-Handling                > "VlObj"           (6x0,40+13x0,90)/9   = 1,5667                                                   ;
;   --•  ActiveX Property-Handling              > "VlPrp"           (3x0,85+5x0,40)/3    = 1,5167                                                   ;
;   --•  Curve Measurement                      > "VlCrv"           (11x0,85+0x0,00)/18  = 0,5194                                                   ;
;   --•  Dictionary                             > "VlDic"           (4x0,75+0x0,00)/5    = 0,6000                                                   ;
;   --•  Handling Drawing Objects               > "VlDrw"           (6x0,70+0x0,00)/13   = 0,3231                                                   ;
;   --•  Reactors                               > "VlRct"           (3x0,10+0x0,00)/44   = 0,0068                                                   ;
;   --•  VLX Namespace                          > "VlSpc"           (0x0,00+0x0,00)/11   = 0,0000                                                   ;
;   --•  Namespace Communication                > "VlCom"           (0x0,00+0x0,00)/4    = 0,0000                                                   ;
;                                                                                                                                                   ;

;                                                   []-----------------------------------------[]                                                   ;

;--- Common local variable's name for the programs (Declare all the local variable of programs is not an option !)                                  ;
;                                                                                                                                                   ;
;                                                                   --- Entity ---                                                                  ;
;   --•  name         > Entity name as <Entity name: ab2e580> (= primary ename)                                                                     ;
;   --•  vl-name      > Entity name as #<VLA-OBJECT IAcadBlockReference 0000000038584688> (= primary VLA-Object)                                    ;
;   --•  ent          > Entity name as <Entity name: ab2e580> (= secondary ename)                                                                   ;
;   --•  vl-ent       > Entity name as #<VLA-OBJECT IAcadBlockReference 0000000038584688> (= secondary VLA-Object)                                  ;
;   --•  entlist      > DXF list obtained with (entget)                                                                                             ;
;   --•  newlist      > DXF list modified or obtained with (entmod) when you want to keep the 'entlist' value                                       ;
;                                                                                                                                                   ;
;                                                               --- Selection Set ---                                                               ;
;   --•  jsel         > Selection set name as <Selection set: 7a> (= primary name)                                                                  ;
;   --•  ssel         > Selection set name as <Selection set: 7a> (= secondary name)                                                                ;
;                                                                                                                                                   ;
;                                                                  --- Counter ---                                                                  ;
;   --•  i            > Counting variable for loop (while), (repeat), (foreach), ... or the number of objects                                       ;
;   --•  n            > Counting variable for the numbering of objects or their position in a list                                                  ;
;                                                                                                                                                   ;
;                                                                    --- List ---                                                                   ;
;   --•  lst          > List for global use, generally obtained by using (cons) in a loop (= primary name)                                          ;
;   --•  pt-list      > List of points coordinates, generally obtained by using (get-pt-list)                                                       ;
;   --•  att-list     > List of block's attributes, generally obtained by using (get-att-list)                                                      ;
;   --•  dyn-list     > List of block's dynamic properties, generally obtained by using (get-DynProp-list)                                          ;
;   --•  layout-list  > List of layouts, generally obtained by using (layoutlist)                                                                   ;
;   --•  layer-list   > List of layers, generally obtained by using (flt_tbl "LAYER")                                                               ;
;   --•  bloc-list    > List of block's definitions, generally obtained by using (flt_tbl "BLOCK")                                                  ;
;                                                                                                                                                   ;
;                                                                   --- String ---                                                                  ;
;   --•  str          > String for global use, generally used for (substr)                                                                          ;
;   --•  msg          > String used for prompting a message in command line's historic, alert message, error's message or dialog_box                ;
;   --•  search       > String used for relative search, generally used for (wcmatch)                                                               ;
;   --•  tag          > Key of pair list, generally used as search key for (assoc)                                                                  ;
;   --•  value        > Value of pair list, generally associated with a search key for (assoc)                                                      ;
;   --•  *-old        > String representing an old value                                                                                            ;
;   --•  *-new        > String representing a new value                                                                                             ;
;                                                                                                                                                   ;
;                                                                 --- Geometric ---                                                                 ;
;   --•  pt           > Coordinates (x y) or (x y z) of a point, generally obtained by using (getpoint)                                             ;
;   --•  ang          > Angle expressed in radian, generally used for (polar)                                                                       ;
;   --•  dist         > Algebric distance, generally used for (vlax-curve-) or (polar)                                                              ;
;                                                                                                                                                   ;
;                                                               --- Loop Variable ---                                                               ;
;   --•  x            > Variable associated for common use of (mapcar '(lambda)) for single argument                                                ;
;   --•  layout       > Name of a specific layout, generally used for (foreach)                                                                     ;
;   --•  layer        > Name of a specific layer, generally used for (foreach)                                                                      ;
;   --•  blc          > Name of a specific block, generally used for (foreach)                                                                      ;
;                                                                                                                                                   ;
;                                                                   --- Method ---                                                                  ;
;   --•  mode         > Value specified by user with (getkword) to determine how the program will work with (cond)                                  ;
;   --•  chx          > Answer specified by user with (getkword) to a "Yes/No" question, could be use with (while)                                  ;
;   --•  flag         > Numeric value (integer) to determine the global functionnality of a function                                                ;
;                                                                                                                                                   ;

;                                                   []-----------------------------------------[]                                                   ;

;--- Some tips for good using the command's file definition :                                                                                       ;
;                                                                                                                                                   ;
;                                                            --- Version of functions ---                                                           ;
; Each function possess a specific string representing the version number. After any modification, this version number have to be updated properly. ;
; At the creation of a named function (for common use), a new file will be created based on the model file "_XxXxx . FunctionName.lsp" with all the ;
; informations needed in commentaries.                                                                                                              ;
;   --•  _XxXxx       > represents the classification's code, like "BaLst", "DtXdt", ... for example                                                ;
;   --•  FunctionName > represents the name of the function defined in the file                                                                     ;
; For each modification, an explanation of what was modified since the last modification is needed. For that, you will need to write the version    ;
; number with the explanation next to the last line.                                                                                                ;
; An update of the file "Developpement LISP - Fichier de suivi" will be needed as soon as possible !                                                ;
;                                                                                                                                                   ;
; Each version number are based on 3 digit, spaced by a ".", representing each modification level -> #.#.#                                          ;
; See the following explanation for each modification level and how version number works :                                                          ;
;   --•  Level n°1 - Major modification                                                                                                             ;
;     It's corresponding to the first digit of the version number. It's concerning any addition or suppression of one or several functionnalities   ;
;     that have a influence on the global use of the function. For a major modification, level 2 and 3 are reset to 0.                              ;
;                                                                                                                                                   ;
;   --•  Level n°2 - Intermediate modification                                                                                                      ;
;     It's corresponding to the second digit of the version number. It's concerning any modifications on existing functionnalities but if the use   ;
;     the function is changed from the point of view of the user, it's considered as a major modification (like addition or suppression of user's   ;
;     input). For a intermediate modification, level 3 is reset to 0.                                                                               ;
;                                                                                                                                                   ;
;   --•  Level n°3 - Minor modification                                                                                                             ;
;     It's corresponding to the third digit of the version number. It's concerning any bug's correction, writing simplification, addition or        ;
;     suppression of variable type check, ... Any modification of use will be considered as intermediate modification (level 2).                    ;
;                                                                                                                                                   ;
;                                                          --- Existing function's list ---                                                         ;
;   --•  "BaAri" --> fixdiv                                         | v1.0.1 - 25/06/2020 (Luna)                                                    ;
;   --•  "BaAri" --> LM:rand                                        | v1.0.0 - 24/06/2020 (LeeMac)                                                  ;
;   --•  "BaAri" --> LM:randrange                                   | v1.0.0 - 24/06/2020 (LeeMac)                                                  ;
;   --•  "BaEqc" --> lst-equal                                      | v1.1.1 - 21/06/2020 (Luna)                                                    ;
;   --•  "BaLst" --> DXF_List                                       | v1.2.1 - 07/07/2020 (Luna)                                                    ;
;   --•  "BaLst" --> get-DXF-list                                   | v1.0.0 - 19/06/2020 (Luna)                                                    ;
;   --•  "BaLst" --> get-DXF-value                                  | v1.0.0 - 19/06/2020 (Luna)                                                    ;
;   --•  "BaLst" --> get-pattern-list                               | v2.0.0 - 24/03/2020 (Luna)                                                    ;
;   --•  "BaLst" --> prompt-list                                    | v1.0.0 - 22/03/2021 (Luna)                                                    ;
;   --•  "BaLst" --> remove-double                                  | v1.0.0 - 18/02/2020 (Luna)                                                    ;
;   --•  "BaLst" --> sort-cons                                      | v1.0.1 - 25/06/2020 (Luna)                                                    ;
;   --•  "BaLst" --> sort-list                                      | v1.2.0 - 25/06/2020 (Luna)                                                    ;
;   --•  "BaLst" --> sublist                                        | v1.1.0 - 24/06/2020 (Luna)                                                    ;
;                                                                                                                                                   ;
;   --•  "UtGeo" --> get-pt-list                                    | v2.0.1 - 21/06/2020 (Luna)                                                    ;
;   --•  "UtGeo" --> osnap-poly                                     | v1.0.0 - 19/06/2020 (Luna)                                                    ;
;                                                                                                                                                   ;
;   --•  "DtObj" --> _putprefix                                     | v1.0.1 - 14/01/2021 (Luna)                                                    ;
;   --•  "DtObj" --> _putsuffix                                     | v1.0.1 - 14/01/2021 (Luna)                                                    ;
;   --•  "DtObj" --> Add-Poly2D-Point                               | v1.0.0 - 19/06/2020 (Luna)                                                    ;
;   --•  "DtObj" --> Explore-DXF                                    | v2.1.1 - 20/05/2021 (Luna)                                                    ;
;   --•  "DtSel" --> select-filter                                  | v3.0.0 - 20/04/2021 (Luna)                                                    ;
;   --•  "DtSyt" --> flt_tbl                                        | v3.0.2 - 21/06/2020 (Luna)                                                    ;
;                                                                                                                                                   ;
;   --•  "VlCol" --> vla-collection->list                           | v1.1.0 - 07/03/2021 (Luna)                                                    ;
;                                                                                                                                                   ;
;                                                          --- Ongoing function's list ---                                                          ;
;   --•  "BaAri" --> acos                                           | v#.#.# - ##/##/#### (Luna)                                                    ;
;   --•  "BaAri" --> ang-conv                                       | v#.#.# - ##/##/#### (Luna)                                                    ;
;   --•  "BaAri" --> asin                                           | v#.#.# - ##/##/#### (Luna)                                                    ;
;   --•  "BaAri" --> tan                                            | v#.#.# - ##/##/#### (Luna)                                                    ;
;   --•  "BaEqc" --> pt-member                                      | v#.#.# - ##/##/#### (Luna)                                                    ;
;   --•  "BaLst" --> divlist                                        | v#.#.# - ##/##/#### (Luna)                                                    ;
;   --•  "BaStr" --> space                                          | v#.#.# - ##/##/#### (Luna)                                                    ;
;   --•  "BaStr" --> str2lst                                        | v1.0.0 - 11/01/2016 (BonusCAD)                                                ;
;   --•  "BaStr" --> Sup-Incr                                       | v#.#.# - ##/##/#### (LeeMac > Luna)                                           ;
;   --•  "BaStr" --> Sup-Incr-Number                                | v#.#.# - ##/##/#### (LeeMac > Luna)                                           ;
;   --•  "BaStr" --> Sup-Incr-Alpha                                 | v#.#.# - ##/##/#### (LeeMac > Luna)                                           ;
;                                                                                                                                                   ;
;   --•  "UtDac" --> atol                                           | v#.#.# - ##/##/#### (Luna)                                                    ;
;   --•  "UtDac" --> rtol                                           | v#.#.# - ##/##/#### (Luna)                                                    ;
;   --•  "UtDis" --> unit-prompt                                    | v#.#.# - ##/##/#### (Luna)                                                    ;
;   --•  "UtGeo" --> get-seg-list                                   | v#.#.# - ##/##/#### (Luna)                                                    ;
;   --•  "UtGeo" --> segsel                                         | v#.#.# - ##/##/#### (Luna)                                                    ;
;   --•  "UtGeo" --> trans_SCG-rt                                   | v#.#.# - ##/##/#### (Luna)                                                    ;
;   --•  "UtGeo" --> trans_SCO                                      | v#.#.# - ##/##/#### (Luna)                                                    ;
;   --•  "UtCom" --> get-date                                       | v#.#.# - ##/##/#### (Luna)                                                    ;
;   --•  "UtUse" --> get-string-or-entity                           | v1.0.0 - 25/03/2020 ((gile))                                                  ;
;   --•  "UtUse" --> ListBox                                        | v1.1.1 - 21/06/2020 (BonusCAD > Luna)                                         ;
;                                                                                                                                                   ;
;   --•  "DtXdt" --> get-Xdata                                      | v#.#.# - ##/##/#### (Luna)                                                    ;
;   --•  "DtObj" --> Array-Def                                      | v#.#.# - ##/##/#### (Luna)                                                    ;
;   --•  "DtObj" --> BlockEntity-layer                              | v#.#.# - ##/##/#### (Luna)                                                    ;
;   --•  "DtObj" --> set-date-TitleBlock                            | v1.0.1 - 21/06/2020 (Luna)                                                    ;
;   --•  "DtObj" --> VP-layer-list                                  | v#.#.# - ##/##/#### (Luna)                                                    ;
;   --•  "DtSel" --> LM:ssboundingbox                               | v1.0.0 - ##/##/#### (LeeMac)                                                  ;
;   --•  "DtSyt" --> get-layout-list                                | v#.#.# - ##/##/#### (Luna)                                                    ;
;   --•  "DtSyt" --> get-layout-position                            | v#.#.# - ##/##/#### (Luna)                                                    ;
;   --•  "DtSyt" --> set-layout-position                            | v#.#.# - ##/##/#### (Luna)                                                    ;
;   --•  "DtSyt" --> layer-check                                    | v1.0.1 - 21/06/2020 (Luna)                                                    ;
;                                                                                                                                                   ;
;   --•  "VlCrv" --> get-AlignPoint-AtDist                          | v#.#.# - ##/##/#### (Luna)                                                    ;
;   --•  "VlPrp" --> get-array-properties                           | v1.0.1 - 21/06/2020 (Luna)                                                    ;
;   --•  "VlPrp" --> set-layout-name                                | v#.#.# - ##/##/#### (Luna)                                                    ;
;   --•  "VlPrp" --> get-att-list                                   | v#.#.# - ##/##/#### (Luna)                                                    ;
;   --•  "VlPrp" --> set-att-value                                  | v#.#.# - ##/##/#### (Luna)                                                    ;
;   --•  "VlPrp" --> set-att-list                                   | v#.#.# - ##/##/#### (Luna)                                                    ;
;   --•  "VlPrp" --> get-DynProp-list                               | v#.#.# - ##/##/#### (LeeMac > Luna)                                           ;
;   --•  "VlPrp" --> set-DynProp-value                              | v#.#.# - ##/##/#### (LeeMac > Luna)                                           ;
;   --•  "VlPrp" --> set-DynProp-list                               | v#.#.# - ##/##/#### (Luna)                                                    ;
;   --•  "VlPrp" --> get-visibility-name                            | v#.#.# - ##/##/#### (LeeMac)                                                  ;
;   --•  "VlPrp" --> get-DynProp-Allowedvalues                      | v#.#.# - ##/##/#### (Luna)                                                    ;
;                                                                                                                                                   ;

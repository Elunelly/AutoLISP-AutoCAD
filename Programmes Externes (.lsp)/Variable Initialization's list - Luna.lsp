;-- In order to initialize properly each drawing when opened, sets a list of variables to desired value for each one of them. Made on Luna's preferences...
(princ "\nInitializing variables...")
(setq $var$
  (list
    (cons "ANNOAUTOSCALE" -4)
    (cons "APBOX" 1)
    (cons "APERTURE" 5)
    (cons "ATTDIA" 1)
    (cons "ATTMODE" 1)
    (cons "ATTREQ" 1)
    (cons "AUPREC" 1)
    (cons "CMDDIA" 1)
    (cons "CMDECHO" 1)
    (cons "DEMANDLOAD" 3)
    (cons "DIMZIN" 0)
    (cons "DRAGMODE" 2)
    (cons "EDGEMODE" 0)
    (cons "FILEDIA" 1)
    (cons "FILETABPREVIEW" 0)
    (cons "FILETABTHUMBHOVER" 0)
    (cons "FRAME" 2)
    (cons "GRIPS" 2)
    (cons "HIGHLIGHT" 1)
    (cons "HPDLGMODE" 1)
    (cons "HPQUICKPREVIEW" 0)
    (cons "IMAGEFRAME" 2)
    (cons "INDEXCTL" 3)
    (cons "INSUNITS" 6)
    (cons "INSUNITSDEFSOURCE" 6)
    (cons "INSUNITSDEFTARGET" 6)
    (cons "LAYOUTREGENCTL" 1)
    (cons "LEGACYCTRLPICK" 0)
    (cons "LOGFILEMODE" 0)
;    (cons "LOGFILEPATH" "C:\\Users\\lphilip\\appdata\\local\\autodesk\\autocad 2022\\r24.1\\fra\\")
    (cons "LUPREC" 2)
    (cons "MBUTTONPAN" 1)
    (cons "MEASUREINIT" 1)
    (cons "MEASUREMENT" 1)
    (cons "MODEMACRO" "$(edtime,$(-,$(getvar,date),$(getvar,tdupdate)),HH:MM:SS)")
    (cons "MIRRTEXT" 0)
    (cons "NOMUTT" 0)
    (cons "OSNAPCOORD" 2)
    (cons "OSNAPZ" 1)
    (cons "PALETTEOPAQUE" 1)
    (cons "PDMODE" 35)
    (cons "PDSIZE" 0.05)
    (cons "PICKADD" 2)
    (cons "PICKAUTO" 5)
    (cons "PICKBOX" 3)
    (cons "PICKDRAG" 2)
    (cons "PICKFIRST" 1)
    (cons "PICKSTYLE" 1)
    (cons "PLINETYPE" 2)
    (cons "PLINEWID" 0)
    (cons "POLARANG" (/ pi 2.))
    (cons "POLARMODE" 0)
    (cons "PROJMODE" 1)
    (cons "QPMODE" -1)
    (cons "REGENMODE" 1)
    (cons "ROLLOVERTIPS" 0)
    (cons "SDI" 0)
    (cons "SELECTIONPREVIEW" 3)
    (cons "SHORTCUTMENU" 11)
    (cons "TEXTEVAL" 0)
    (cons "TEXTFILL" 1)
    (cons "UCSDETECT" 0)
    (cons "UCSFOLLOW" 0)
    (cons "VISRETAIN" 1)
    (cons "WSCURRENT" "2D - Express Tool")
    (cons "XLOADCTL" 2)
    (cons "XREFOVERRIDE" 0)
  )
)
(mapcar '(lambda (x) (setvar (car x) (cdr x))) $var$)
(princ (strcat "\nSuccessfully defined " (itoa (length $var$)) " variables !"))
(setq $var$ nil)
(princ)

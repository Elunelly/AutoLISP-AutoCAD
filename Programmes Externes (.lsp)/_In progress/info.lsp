(defun c:info (/ myerr dxf del_ss tran_ang tran_zb add_solid add_text dis_info
	         acaddoc olderr oldvar ss loop gr pt ent oldent)
  (defun myerr (msg)
    (del_ss ss)
    (setq *error* olderr)
  )
  (defun dxf (ent n)
    (if	(= (type ent) 'ename)
      (setq ent (entget ent))
    )
    (cdr (assoc n ent))
  )
  (defun del_ss (ss / n)
    (setq n -1)
    (repeat (sslength ss)
      (entdel (ssname ss (setq n (1+ n))))
    )
    (if oldent (redraw oldent 4))
  )
  (defun tran_ang (ang)
    (strcat (rtos (* ang (/ 180 pi)) 2 (getvar "auprec")) " %%D")
  )
  (defun tran_zb (nm / zb)
    (if (= (type nm) 'int) (setq zb (dxf ent nm)) (setq zb nm))
    (strcat (rtos (car zb) 2 lup) "," (rtos (cadr zb) 2 lup) (if (caddr zb) (strcat "," (rtos (caddr zb) 2 lup)) ""))
  )
  (defun add_solid (p1 p2 p3 p4)
    (entmakex (list (cons 0 "SOLID") (cons 100 "AcDbEntity") (cons 62 9) (cons 100 "AcDbTrace")
                    (cons 10 p1)(cons 11 p2) (cons 12 p3) (cons 13 p4) (cons 210 (trans (getvar "viewdir") 1 0))
    ))
  )
  (defun add_text (pt h txt)
    (entmakex (list (cons 0 "TEXT") (cons 100 "AcDbEntity") (cons 62 5) (cons 100 "AcDbText")
                    (cons 10 pt) (cons 40 h) (cons 1 txt) (cons 50 0.0) (cons 7 "HABILLAGE") (cons 72 0) (cons 73 0)
                    (cons 210 (trans (getvar "viewdir") 1 0))
    ))
  )
  (defun dis_info (ent / obj laynm name lup lst h high width ang n dis)
    (setq obj (vlax-ename->vla-object ent)
          laynm	(strcat "Calque : " (dxf ent 8))
	  name	(dxf ent 0)
	  lup (getvar "luprec")
    )
    (cond
      ((= name "3DFACE")
        (setq lst (list "3DFACE"))
      )
      ((= name "3DSOLID")
        (setq lst (list "3DSOLID"
		        (strcat "Centroid : " (tran_zb (vlax-safearray->list (vlax-variant-value (vla-get-Centroid obj)))))
		        (strcat "MomentOfInertia : " (tran_zb (vlax-safearray->list (vlax-variant-value (vla-get-MomentOfInertia obj)))))
		        (strcat "RadiiOfGyration : " (tran_zb (vlax-safearray->list (vlax-variant-value (vla-get-RadiiOfGyration obj)))))
	))
      )
      ((= name "ACAD_PROXY_ENTITY")
        (setq lst (list "ACAD_PROXY_ENTITY"))
      )
      ((= name "ARC")
        (setq lst (list "ARC"
		        (strcat "Premier Point : " (tran_zb 10))
		        (strcat "Rayon : "   (rtos (vla-get-radius obj) 2 lup))
		        (strcat "TotalAngle : " (tran_ang (vla-get-TotalAngle obj)))
		        (strcat "StartAngle : " (tran_ang (vla-get-StartAngle obj)))
		        (strcat "EndAngle : " (tran_ang (vla-get-EndAngle obj)))
		        (strcat "ArcLength : " (rtos (vla-get-ArcLength obj) 2 lup))
		        (strcat "Aire : "   (rtos (vla-get-Area obj) 2 lup))
	))
      )
      ((= name "ATTDEF")
        (setq lst (list "ATTDEF"
		        (strcat "Premier Point : " (tran_zb 10))
		        (strcat "TagString : " (vla-get-TagString obj))
		        (strcat "PromptString : " (vla-get-PromptString obj))
		        (strcat "TextString : " (vla-get-TextString obj))
		        (strcat "Height : " (rtos (vla-get-Height obj) 2 lup))
		        (strcat "Rotation : " (tran_ang (vla-get-Rotation obj)))
		        (strcat "StyleName : " (vla-get-StyleName obj))
	))
      )
      ((= name "ATTRIB")
        (setq lst (list "ATTRIB"
		        (strcat "Premier Point : " (tran_zb 10))
		        (strcat "TagString : " (vla-get-TagString obj))
		        (strcat "TextString : " (vla-get-TextString obj))
		        (strcat "Height : " (rtos (vla-get-Height obj) 2 lup))
		        (strcat "Rotation : " (tran_ang (vla-get-Rotation obj)))
		        (strcat "StyleName : " (vla-get-StyleName obj))
        ))
      )
      ((= name "CIRCLE")
        (setq lst (list "CIRCLE"
	                (strcat "Premier Point : " (tran_zb 10))
	                (strcat "radius : " (rtos (vla-get-radius obj) 2 lup))
	                (strcat "Circumference : " (rtos (vla-get-Circumference obj) 2 lup))
	                (strcat "Aire : " (rtos (vla-get-Area obj) 2 lup))
        ))
      )
      ((= name "DIMENSION")
        (setq lst (list "DIMENSION"
		        (strcat "StyleName : " (vla-get-StyleName obj))
		        (strcat "TextStyle : " (vla-get-TextStyle obj))
		        (strcat "TextHeight : " (rtos (vla-get-TextHeight obj) 2 lup))
		        (strcat	"替带文字 : " (if (= (dxf ent 1) "") "无" (dxf ent 1)))
        ))
      )
      ((= name "ELLIPSE")
        (setq lst (list	"ELLIPSE"
		        (strcat "Premier Point : " (tran_zb 10))
		        (strcat "MajorRadius : " (rtos (vla-get-MajorRadius obj) 2 lup))
		        (strcat "MinorRadius : " (rtos (vla-get-MinorRadius obj) 2 lup))
		        (strcat	"StartAngle : " (tran_ang (vla-get-StartAngle obj)))
		        (strcat	"EndAngle : " (tran_ang (vla-get-EndAngle obj)))
		        (strcat "Coordonn閑s : " (rtos (vlax-curve-getDistAtParam Obj (vlax-curve-getEndParam Obj)) 2 lup))
		        (strcat	"Aire : "	(rtos (vla-get-Area obj) 2 lup))
        ))
      )
      ((= name "HATCH")
        (setq lst (list	"HATCH"
		        (strcat "PatternName : " (vla-get-PatternName obj))
		        (strcat	"PatternAngle : "	(tran_ang (vla-get-PatternAngle obj)))
		        (strcat "PatternScale : " (rtos (vla-get-PatternScale obj) 2 lup))
		        (strcat "AssociativeHatch : " (if (= (vla-get-AssociativeHatch obj) :vlax-false) "关闭" "打开"))
		        (strcat "HatchStyle : " (nth (vla-get-HatchStyle obj) '("普通" "外部" "忽略")))
        ))
      )
      ((= name "IMAGE")
        (setq lst (list "IMAGE"
		        (strcat "Premier Point : " (tran_zb 10))
		        (strcat "Coordonn閑s : " (rtos (car (dxf ent 13)) 2 lup) "X" (rtos (cadr (dxf ent 13)) 2 lup))
        ))
      )
      ((= name "INSERT")
        (setq lst (list "INSERT"
		        (strcat "Premier Point : " (tran_zb 10))
		        (strcat "Name : " (vla-get-Name obj))
		        (strcat "XScaleFactor : " (rtos (vla-get-XScaleFactor obj) 2 lup))
		        (strcat "YScaleFactor : " (rtos (vla-get-YScaleFactor obj) 2 lup))
		        (strcat "ZScaleFactor : " (rtos (vla-get-ZScaleFactor obj) 2 lup))
		        (strcat "Rotation : " (tran_ang (vla-get-Rotation obj)))
        ))
      )
      ((= name "LEADER")
        (setq lst (list "LEADER"
	                (strcat "StyleName : " (vla-get-StyleName obj))
	                (strcat "Type : " (nth (vla-get-Type obj) '("无箭头直线" "无箭头曲线" "箭头直线" "箭头曲线")))
	                (strcat "TextGap : " (rtos (vla-get-TextGap obj) 2 lup))
		        (strcat	"VerticalTextPosition : "	(nth (vla-get-VerticalTextPosition obj) '("置中" "上方" "外部" "JIS")))
        ))
      )
      ((= name "LINE")
        (setq lst (list "LINE"
                        (strcat "Premier Point : " (tran_zb 10))
                        (strcat "Second Point : " (tran_zb 11))
		        (strcat "Longueur : " (rtos (vla-get-length obj) 2 lup))
		        (strcat "Angle : " (tran_ang (vla-get-angle obj)))
        ))
      )
      ((= name "LWPOLYLINE")
        (setq n (fix (vlax-curve-getparamatpoint obj (vlax-curve-getclosestpointto obj (trans pt 1 0)))))
        (setq dis (vlax-curve-getdistatparam obj (1+ n)))
        (if (not dis) (setq dis (vlax-curve-getdistatparam obj (1- n))))
        (setq lst (list "LWPOLYLINE"
		        (strcat "ConstantWidth : " (if (dxf ent 43) (rtos (vla-get-ConstantWidth obj) 2 lup) "变宽度"))
		        (strcat "Closed : " (if (= (vla-get-Closed obj) :vlax-false) "Non" "Oui"))
		        (strcat "Longueur : " (rtos (vlax-curve-getDistAtParam Obj (vlax-curve-getEndParam Obj)) 2 lup))
		        (strcat "Aire : " (rtos (vla-get-Area obj) 2 lup))
		        (strcat "Longueur : " (rtos (abs (- dis (vlax-curve-getdistatparam obj n))) 2 lup))
        ))
      )
      ((= name "MLINE")
        (setq lst (list "MLINE"
		        (strcat "StyleName : " (vla-get-StyleName obj))
		        (strcat "Facteur d'閏helle : " (rtos (dxf ent 40) 2 lup))
		        (strcat "Justification : " (nth (dxf ent 70) '("Haut" "Z閞o" "Bas")))
        ))
      )
      ((= name "MTEXT")
        (setq lst (list "MTEXT"
		        (strcat "Point d'Insertion : " (tran_zb 10))
		        (strcat "Height : " (rtos (vla-get-Height obj) 2 lup))
		        (strcat "Rotation : " (tran_ang (vla-get-Rotation obj)))
		        (strcat "Width : " (rtos (vla-get-Width obj) 2 lup))
		        (strcat "StyleName : " (vla-get-StyleName obj))
		        (strcat	"Justification : "	(nth (1- (vla-get-AttachmentPoint obj))
			                  '("Haut-Gauche" "Haut-Centre" "Haut-Droit" "Milieu-Gauche" "Milieu-Centre" "Milieu-Droit" "Bas-Gauche" "Bas-Centre" "Bas-Droit"))
			)
        ))
      )
      ((or (= name "OLEFRAME") (= name "OLE2FRAME"))
        (setq lst (list "OLEFRAME"))
      )
      ((= name "POINT")
        (setq lst (list "POINT"
                        (strcat "Point d'Insertion : " (tran_zb 10))
        ))
      )
      ((= name "POLYLINE")
        (cond
          ((= (vla-get-objectname obj) "AcDb3dPolyline")
            (setq n (fix (vlax-curve-getparamatpoint obj (vlax-curve-getclosestpointto obj (trans pt 1 0)))))
            (setq dis (vlax-curve-getdistatparam obj (1+ n)))
            (if (not dis) (setq dis (vlax-curve-getdistatparam obj (1- n))))
            (setq lst (list "AcDb3dPolyline"
                            (strcat "Closed : " (if (= (logand (dxf ent 70) 1) 1) "Oui" "Non"))
                            (strcat "Type : " (nth (vla-get-Type obj) '("无" "二次" "三次")))
                            (strcat "Longueur : " (rtos (vlax-curve-getDistAtParam Obj (vlax-curve-getEndParam Obj)) 2 lup))
                            (strcat "Longueur : " (rtos (abs (- dis (vlax-curve-getdistatparam obj n))) 2 lup))
            ))
          )
          ((= (vla-get-objectname obj) "AcDb2dPolyline")
            (setq n (fix (vlax-curve-getparamatpoint obj (vlax-curve-getclosestpointto obj (trans pt 1 0)))))
            (setq dis (vlax-curve-getdistatparam obj (1+ n)))
            (if (not dis) (setq dis (vlax-curve-getdistatparam obj (1- n))))
            (setq lst (list "AcDb2dPolyline"
		            (strcat "Closed : " (if (= (vla-get-Closed obj) :vlax-false) "Non" "Oui"))
		            (strcat "Type : " (nth (vla-get-Type obj) '("无" "拟合曲线" "二次" "三次")))
		            (strcat "Longueur : " (rtos (vlax-curve-getDistAtParam Obj (vlax-curve-getEndParam Obj)) 2 lup))
		            (strcat "Aire : " (rtos (vla-get-Area obj) 2 lup))
		            (strcat "Longueur : " (rtos (abs (- dis (vlax-curve-getdistatparam obj n))) 2 lup))
            ))
          )
          (T
            (setq lst (list "POLYLINE"))
          )
        )
      )
      ((= name "RAY")
        (setq lst (list "RAY"
                        (strcat "Point d'Insertion : " (tran_zb 10))
        ))
      )
      ((= name "REGION")
        (setq lst (list "REGION"
		        (strcat "Perimeter : " (rtos (vla-get-Perimeter obj) 2 lup))
		        (strcat "Aire : " (rtos (vla-get-Area obj) 2 lup))
		        (strcat "Centroid : " (tran_zb (vlax-safearray->list (vlax-variant-value (vla-get-Centroid obj)))))
		        (strcat "MomentOfInertia : " (tran_zb (vlax-safearray->list (vlax-variant-value (vla-get-MomentOfInertia obj)))))
		        (strcat "RadiiOfGyration : " (tran_zb (vlax-safearray->list (vlax-variant-value (vla-get-RadiiOfGyration obj)))))
        ))
      )
      ((= name "SHAPE")
        (setq lst (list	"SHAPE"
		        (strcat "Point d'Insertion : " (tran_zb 10))
		        (strcat "Height : " (rtos (vla-get-Height obj) 2 lup))
		        (strcat "ScaleFactor : " (rtos (vla-get-ScaleFactor obj) 2 lup))
		        (strcat	"Rotation : "	(tran_ang (vla-get-Rotation obj)))
		        (strcat	"ObliqueAngle : "	(tran_ang (vla-get-ObliqueAngle obj)))
        ))
      )
      ((= name "SOLID")
        (setq lst (list "SOLID"))
      )
      ((= name "SPLINE")
        (setq lst (list "SPLINE"
		        (strcat "Closed : " (if (= (vla-get-Closed obj) :vlax-false) "Non" "Oui"))
		        (strcat "IsPlanar : " (if (= (vla-get-IsPlanar obj) :vlax-false) "不是" "是"))
		        (strcat "Degree : " (rtos (vla-get-Degree obj) 2 0))
		        (strcat "FitTolerance : " (rtos (vla-get-FitTolerance obj) 2 lup))
		        (strcat "Longueur : " (rtos (vlax-curve-getDistAtParam Obj (vlax-curve-getEndParam Obj)) 2 lup))
		        (strcat "Aire : " (if (= (vla-get-IsPlanar obj) :vlax-false) "无" (rtos (vla-get-Area obj) 2 lup)))
        ))
      )
      ((= name "TEXT")
        (setq lst (list "TEXT"
		        (strcat "Point d'Insertion : " (tran_zb 10))
		        (strcat "Height : " (rtos (vla-get-Height obj) 2 lup))
		        (strcat "ScaleFactor : " (rtos (vla-get-ScaleFactor obj) 2 lup))
		        (strcat	"Rotation : "	(tran_ang (vla-get-Rotation obj)))
		        (strcat "StyleName : " (vla-get-StyleName obj))
		        (strcat	"Justification : "	(nth (vla-get-Alignment obj)
			                  '("Gauche" "Centre" "Droite" "Align�" "Milieu" "Ajuster" "Haut-Gauche" "Haut-Centre"
			                    "Haut-Droit" "Milieu-Gauche" "Milieu-Centre" "Milieu-Droit" "Bas-Gauche" "Bas-Centre" "Bas-Droit"))
			)
			(strcat	"ObliqueAngle : "	(tran_ang (vla-get-ObliqueAngle obj)))
        ))
      )
      ((= name "TOLERANCE")
        (setq lst (list	"TOLERANCE"
		        (strcat "Point d'Insertion : " (tran_zb 10))
		        (strcat "StyleName : " (vla-get-StyleName obj))
		        (strcat "TextStyle : " (vla-get-TextStyle obj))
		        (strcat "TextHeight : " (rtos (vla-get-TextHeight obj) 2 lup))
        ))
      )
      ((= name "TRACE")
        (setq lst (list "TRACE"))
      )
      ((= name "VERTEX")
        (setq lst (list "VERTEX"
		        (strcat "Point d'Insertion : " (tran_zb 10))
		        (strcat "Largeur de d閜art : " (rtos (dxf ent 40) 2 lup))
		        (strcat "Largeur de fin : " (rtos (dxf ent 41) 2 lup))
		        (strcat "Courbure : " (rtos (dxf ent 42) 2 lup))
        ))
      )
      ((= name "VIEWPORT")
        (setq lst (list "VIEWPORT"
		        (strcat "Centre : " (tran_zb 10))
		        (strcat "Width : " (rtos (vla-get-Width obj) 2 lup))
		        (strcat "Height : " (rtos (vla-get-Height obj) 2 lup))
        ))
      )
      ((= name "XLINE")
        (setq lst (list "XLINE"
                        (strcat "Premier point : " (tran_zb 10))
        ))
      )
      (T
        (setq lst (list "【未知对象】"))
      )
    )
    (setq lst (append (list (car lst)) (list laynm) (cdr lst))
          ss (ssadd)
          h (/ (getvar "viewsize") 60)
          high (* 1.7 h (length lst))
          width (* 0.75 h (apply 'max (mapcar 'strlen lst)))
          ang (angle (trans (getvar "viewctr") 1 2) (trans pt 1 2))
          pt (trans (mapcar '+ pt (getvar "target")) 1 2)
          ang (cond
                ((>= (/ pi 2) ang 0)
                  (list (list (- (car pt) width) (- (cadr pt) high) (caddr pt)) (list (- (car pt) width) (cadr pt) (caddr pt)))
                )
                ((>= pi ang (/ pi 2))
                  (list (list (+ (car pt) width) (- (cadr pt) high) (caddr pt)) pt)
                )
                ((>= (+ pi (/ pi 2)) ang pi)
                  (list (list (+ (car pt) width) (+ (cadr pt) high) (caddr pt)) (list (car pt) (+ (cadr pt) high) (caddr pt)))
                )
                ((>= (* 2 pi) ang (+ pi (/ pi 2)))
                  (list (list (- (car pt) width) (+ (cadr pt) high) (caddr pt)) (list (- (car pt) width) (+ (cadr pt) high) (caddr pt)))
                )
              )
    )
    (ssadd (add_solid pt (list (caar ang) (cadr pt) (caddr pt)) (list (car pt) (cadar ang) (caddr pt)) (car ang)) ss)
    (setq pt (cadr ang) pt (list (+ (car pt) (* 0.5 h)) (cadr pt) (caddr pt)))
    (setq n -1)
    (repeat (length lst)
      (ssadd (add_text (setq pt (list (car pt) (- (cadr pt) (* 1.6 h)) (caddr pt))) h (nth (setq n (1+ n)) lst)) ss)
    )
  )
  (vl-load-com)
  (setq acaddoc (vla-get-activedocument (vlax-get-acad-object)))
  (vla-startundomark acaddoc)
  (prompt "\n*** Glisser le curseur sur un objet pour afficher ses propri閠閟 ***")
  (setq	olderr *error*
        *error* myerr
        oldvar (list (list "osmode" (getvar "osmode")) (list "fillmode" (getvar "fillmode")))
        ss (ssadd)
        loop T
  )
  (setvar "osmode" 0)
  (setvar "fillmode" 1)
  ;(if (not (tblsearch "style" "info"))
  ;  (progn
  ;    (setq newstyle (vla-add (vla-get-textstyles acaddoc) "info"))
  ;    (vla-put-fontfile newstyle "txt.shx")
  ;    (vla-put-bigfontfile newstyle "hztxt.shx")
  ;    (vlax-release-object newstyle)
  ;  )
  ;)
  (while loop
    (setq gr (grread T 8))
    (cond
      ((or (= (car gr) 12) (= (car gr) 5))
        (setq pt  (cadr gr)
	      ent (nentselp pt)
	      ent (if (and ent (= (type (last (last ent))) 'ename))
		    (last (last ent))
		    (car ent)
		  )
	)
	(if ent
          (if (not (or (equal ent oldent) (ssmemb ent ss)))
            (progn
              (del_ss ss)
              (if (and (= (dxf ent 0) "VERTEX") (dxf ent 330))
                (setq ent (dxf ent 330))
              )
	      (redraw ent 3)
	      (dis_info ent)
	      (setq oldent ent)
            )
          )
          (progn
            (del_ss ss)
            (setq oldent nil ss (ssadd))
          )
        )
      )
      ((= (car gr) 3)
	(if oldent
	  (if (= (getvar "cmdnames") "")
	    (progn
	      (sssetfirst nil (ssadd oldent))
	      (vl-cmdf "_.properties")
	    )
	    (prompt "\n透明调用时无法编辑！")
	  )
	)
      )
      (T (setq loop nil))
    )
  )
  (del_ss ss)
  (if (or (= (car gr) 12) (= (car gr) 25)) (sssetfirst))
  (setq *error* olderr)
  (foreach itm oldvar (setvar (car itm) (cadr itm)))
  (vla-endundomark acaddoc)
  (vlax-release-object acaddoc)
  (princ)
)
(setvar "cmdecho" 0)
(if (not (tblsearch "style" "info"))
  (progn
    (setq oldtxtsty (getvar "textstyle"))
	;cr閍tion du style info avec la commande style fran鏰ise
    (vl-cmdf "-style" "info" "arial.ttf" "0" "1" "0" "n" "n")
    ;(vl-cmdf "_.style" "info" "Arial" "0" "1" "0" "n" "n")
    (setvar "textstyle" oldtxtsty)
    (setq oldtxtsty nil)
  )
)
(prompt "\n*** Tapez info pour lancer : ***")
(princ)

(defun c:circle2lw ( / js ent dxf_ent pt_cen radius fst_pt opp_pt new_ep)
	(while (null (setq js (ssget "_:S" '((0 . "CIRCLE"))))))
	(setq
		ent (ssname js 0)
		dxf_ent (entget ent)
		pt_cen (cdr (assoc 10 dxf_ent))
		radius (cdr (assoc 40 dxf_ent))
		fst_pt (polar pt_cen 0.0 radius)
		opp_pt (polar pt_cen pi radius)
	)
	(princ "\nEpaisseur du cercle <")
	(princ (getvar "PLINEWID"))
	(princ ">: ")
	(initget 68)
	(setq new_ep (getdist))
	(if new_ep (setvar "PLINEWID" new_ep))
	(entmake
		(list
			'(0 . "LWPOLYLINE")
			'(100 . "AcDbEntity")
			(assoc 67 dxf_ent)
			(assoc 410 dxf_ent)
			(assoc 8 dxf_ent)
			(if (assoc 6 dxf_ent) (assoc 6 dxf_ent) '(6 . "BYLAYER"))
			(if (assoc 62 dxf_ent) (assoc 62 dxf_ent) '(62 . 256))
			(if (assoc 370 dxf_ent) (assoc 370 dxf_ent) '(370 . -3))
			(if (assoc 48 dxf_ent) (assoc 48 dxf_ent) '(48 . 1.0))
			'(100 . "AcDbPolyline")
			'(90 . 2)
			'(70 . 1)
			(cons 43 (getvar "PLINEWID"))
			(cons 38 (caddr fst_pt))
			(if (assoc 39 dxf_ent) (assoc 39 dxf_ent) '(39 . 0.0))
			(cons 10 (list (car fst_pt) (cadr fst_pt)))
			'(40 . 0.0)
			'(41 . 0.0)
			'(42 . 1.0)
			(cons 10 (list (car opp_pt) (cadr opp_pt)))
			'(40 . 0.0)
			'(41 . 0.0)
			'(42 . 1.0)
			(assoc 210 dxf_ent)
		)
	)
	(entdel ent)
	(prin1)
)
